# IBM Engineering Requirements Tue May 23 04:57:03 CEST 2023

# Specification: ECU_Requirement
- ReqIF.Name: ECU_Requirement
- Artifact Format: Module

## 629021: General Overview / Document Scope (Heading)
- Artifact Format: Text

### 629020: Document Scope (Heading)
- Artifact Format: Text

#### 629016: <put below a first description of the scope for software requirement specification> (Information)
<put below a first description of the scope for ECU requirement specification>
- Artifact Format: Text

### 629012: Document Specific Glossary (Heading)
- Artifact Format: Text

#### 629013: <put below a definition of first glossary specific terms> (Information)
- Artifact Format: Text

## 629019: System Requirement (Heading)
- Artifact Format: Text
- ChapterName: System Requirements

### 629017 (Information)
<infos relevant for the complete chapter>
Note to the template:
- the example requirements below are independent of each other and are showing the different possibilities of the requirements structure
- Artifact Format: Text

### 629022: ECU 1st Requirement (Heading)
- Artifact Format: Text

#### 629015 (MO_FUNC_REQ)
<description of the requirement in requirements language>
VEHICLE_SYSTEM_BEHAVIOUR
<Optional: description of desired vehicle behavior ("development target")>
CONSTRAINT
<Optional: constraints on the solution space for the requirement>
IMPACT
<Optional: description of possible cross-functional impact of the requirement, or impact on other components>
INFO
<Optional: additional informations about the requirement:
- know-how
- background
- HW dependencies related to the system requirement
- internal signals
- etc>
ASSUMPTION
<Optional: assumptions on the requirement>
- VAR_FUNC_SYS: VAR_Func_sys value
- Verification Criteria: Test Environment:
  Test Bench/Lab-car with hardware setup

  Success Criteria: Verify whether the signal value is correct or not
- Safety Classification: ASIL A
- Status: NEW/CHANGED
- Allocation: SW Allocation
- Artifact Format: Text
- CRQ: RQONE03587423

## 629018: System Non Fonctional Requirements (Heading)
- Artifact Format: Text
- ChapterName: System Non Functional Requirements

### 629014: <description of the non functional requirement in requirements language> (MO_NON_FUNC_REQ)
- CRQ: RQONE03587423
- Safety Classification: ASIL B
- Allocation: Non_Func Allocation
- Verification Criteria: Non Func Test Environment:
  Test Bench/Lab-car with hardware setup

  Success Criteria: Verify whether the signal value is correct or not
- Status: NEW/CHANGED
- VAR_FUNC_SYS: Var_func_sys value 2
- Artifact Format: Text
